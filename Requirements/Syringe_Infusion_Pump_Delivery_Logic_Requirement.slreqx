# Syringe_Infusion_Pump_Delivery_Logic_Requirement

## Syringe_Infusion_Pump_Delivery_Logic_Requirement: References to Syringe Infusion Pump Delivery Logic Requirement.docx (Functional)
References to Microsoft Word document
C:\Users\szhang\Documents\MATLAB\InfusionPumpSeminar\Documents\Syringe Infusion Pump Delivery Logic Requirement.docx

### 1. Architecture: Architecture (Functional)
1. Architecture

#### Simulink_requirement_item_58: Command Inputs (Functional)
1.1 Command Inputs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

##### Simulink_requirement_item_1: Enable Disable Switch (Functional)
1.1.1 Enable/Disable Switch
The controller shall have an On/Off Switch to enable/disable the operation of the infusion pump system.

##### Simulink_requirement_item_2: Bolus Type (Functional)
1.1.2 Bolus Type
The controller shall have the capability to control how the bolus can be delivered. When the bolus bype is 0 no bolus shall be delivered. When bolus type is 1, a single pulse can be generated to deliver a bolus. When the bolus type is 2, the pulses can be configured to have different intensity and duration for four sections.

##### Simulink_requirement_item_3: Number of Repeating Cycles (Functional)
1.1.3 Number of Repeating Cycles
The controller shall have the capability to control the number of repeating cycles of the bolus type.

##### Simulink_requirement_item_4: Bolus Delivery Action Trigger (Functional)
1.1.4 Bolus Delivery Action Trigger
The controller shall have the capability to control when to trigger the bolus delivery.

##### Simulink_requirement_item_5: Normal Bolus Magnitude (Functional)
1.1.5 Normal Bolus Magnitude
The controller shall have the capability to control how many units of medicine can be delivered in one pulse of the normal bolus mode.

##### Simulink_requirement_item_6: Normal Bolus Duration (Functional)
1.1.6 Normal Bolus Duration
The controller shall have the capability to control the duration of the normal bolus pulse.

##### Simulink_requirement_item_7: Quick Bolus Magnitude (Functional)
1.1.7 Quick Bolus Magnitude
The controller shall have the capability to control how many units of medicine can be delivered in each pulse of the quick bolus mode.

##### Simulink_requirement_item_8: Quick Bolus Duration (Functional)
1.1.8 Quick Bolus Duration
The controller shall have the capability to control the duration of the quick bolus pulses.

##### Simulink_requirement_item_9: Pause Time (Functional)
1.1.9 Pause Time
The controller shall have the capability to control how long the system will pause between pulses.

##### Simulink_requirement_item_10: Lower Limit (Functional)
1.1.10 Lower Limit
The controller shall have the capability to set the lower limit of the remaining unit of the reservoir.

##### Simulink_requirement_item_11: Basal Delivery Action Trigger (Functional)
1.1.11 Basal Delivery Action Trigger
The controller shall have the capability to control when to trigger basal delivery and stop basal delivery.

##### Simulink_requirement_item_13: Maximum Basal Delivery Rate (Functional)
1.1.12 Maximum Basal Delivery Rate
The controller shall have the capability to set the maximum allowable value for basal rate. The value should be between 0 and 2 unit/hr

##### Simulink_requirement_item_12: Basal Delivery Rate Setting (Functional)
1.1.13 Basal Delivery Rate Setting
The controller shall have the capability to set the basal delivery rate.

#### Simulink_requirement_item_59: Feedback Input (Functional)
1.2 Feedback Input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

##### Simulink_requirement_item_52: Feedback Angular Speed (Functional)
1.2.1 Feedback: Angular Speed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
The controller shall react to the speed sensor.

##### Simulink_requirement_item_14: Feedback Piston Position (Functional)
1.2.2 Feedback: Piston Position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
The controller shall react to the current piston position.

##### Simulink_requirement_item_15: Feedback Force Sensor (Functional)
1.2.3 Feedback: Force Sensor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
The controller shall react to delivery line pressure

#### 1.3 Outputs: Outputs (Functional)
1.3 Outputs

##### Simulink_requirement_item_16: Motor Control Voltage (Functional)
1.3.1 Motor Control Voltage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
The controller shall be able to control the voltage of the DC motor.

### Simulink_requirement_item_60: Supervisory Logic (Functional)
2. Supervisory Logic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

#### Simulink_requirement_item_17: Bolus Control Chart (Functional)
2.1 Bolus Control Chart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
Based on the input settings the controller shall control accurately how the bolus would be delivered.

##### Simulink_requirement_item_18: System off before start-up (Functional)
2.1.1 System off before start-up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
The bolus delivery shall be disabled before turned on.

##### Simulink_requirement_item_19: System armed after start-up (Functional)
2.1.2 System armed after start-up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
The bolus delivery shall be armed but not active after start-up

##### Simulink_requirement_item_20: Normal Bolus Mode (Functional)
2.1.3 Normal Bolus Mode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
Normal bolus mode shall be armed only when delivery type is set to 1. The delivery action must be triggered.

###### Simulink_requirement_item_21: Normal Bolus Mode Inactive when initially armed (Functional)
2.1.3.1 Normal Bolus Mode Inactive when initially armed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
When normal bolus mode is initially armed, no bolus should be delivered.

###### Simulink_requirement_item_22: Normal Bolus Mode active when triggered (Functional)
2.1.3.2 Normal Bolus Mode active when triggered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
After triggered, bolus can be delivered. The number repeating cycle will be cleaned every time it is triggered. This mode is only possible when the unit remaining is enough for at least one cycle.

###### Simulink_requirement_item_23: During Bolus Delivery (Functional)
2.1.3.3 During Bolus Delivery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
During one cycle of bolus delivery, the stroke magnitude will be calculated based on how many units is set to be completed in the set duration. This states is only available when the desired number of cycles is not yet completed.

###### Simulink_requirement_item_24: Pause After Bolus Delivery (Functional)
2.1.3.4 Pause After Bolus Delivery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
During the pause section of one cycle, no bolus should be delivered. This states is only available when the number of repeating cycle is not finished.

###### Simulink_requirement_item_63: Deactivate Normal Bolus Mode (Functional)
2.1.3.5 Deactivate Normal Bolus Mode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
There are conditions the normal bolus mode can return to the inactive state:

###### Simulink_requirement_item_25: Number of repeating cycle is finished (Functional)
1. Number of repeating cycle is finished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

###### Simulink_requirement_item_26: There is not enough unit remaining to finish the next cycle (Functional)
2. There is not enough unit remaining to finish the next cycle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

###### Simulink_requirement_item_53: The occlusion is detected to be occurring. (Functional)
3. The occlusion is detected to be occurring.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

##### Simulink_requirement_item_48: Quick Bolus Mode (Functional)
2.1.4 Quick Bolus Mode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

###### Simulink_requirement_item_49: Quick Bolus Mode Inactive when initially armed (Functional)
2.1.4.1 Quick Bolus Mode Inactive when initially armed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
When quick bolus mode is initially armed, no bolus should be delivered.

###### Simulink_requirement_item_50: Quick Bolus Mode active when triggered (Functional)
2.1.4.2 Quick Bolus Mode active when triggered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
After triggered, bolus can be delivered. The number repeating cycle will be cleaned every time it is triggered. This mode is only possible when the unit remaining is enough for at least one cycle.

###### 2.1.4.3 Deactivate Quick Bolus Mode: Deactivate Quick Bolus Mode (Functional)
2.1.4.3 Deactivate Quick Bolus Mode
There are conditions the normal bolus mode can return to the inactive state:

###### Simulink_requirement_item_54: Number of repeating cycle is finished (Functional)
1. Number of repeating cycle is finished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

###### Simulink_requirement_item_55: There is not enough unit remaining to finish the next cycle (Functional)
2. There is not enough unit remaining to finish the next cycle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

###### Simulink_requirement_item_56: The occlusion is detected to be occurring. (Functional)
3. The occlusion is detected to be occurring.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

#### Simulink_requirement_item_27: Basal Control Chart (Functional)
2.2 Basal Control Chart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
Based on the input settings the controller shall control accurately how the basal would be delivered.

##### Simulink_requirement_item_28: System off before start-up (Functional)
2.2.1 System off before start-up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
The basal delivery shall be disabled before turned on.

##### Simulink_requirement_item_29: System armed after start-up (Functional)
2.2.2 System armed after start-up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
The basal delivery shall be armed but not active after start-up

##### Simulink_requirement_item_30: System available conditions (Functional)
2.2.3 System available conditions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
In this stage there should be no basal delivery.
1. Before the entering the state ready to start basal delivery, the algorithm is going to check if the remaining amount is above the set lower limit.
2. There should be no occlusion detected.

##### Simulink_requirement_item_31: Algorithm to determine when to start and stop basal delivery (Functional)
2.2.4 Algorithm to determine when to start and stop basal delivery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
The supervisory logic should determine when to start and stop basal delivery based on setting and feedback from the rest of the system. Here are the conditions that could check condition change:
1. Start condition: when the prerequisite of remaining amount is satisfied, the starting point of basal delivery should be triggered by Basal Active signal turn from false to true.
2. Stop condition:
a. User should be able to stop basal delivery by turn Basal Active Signal from true to false
b. During basal delivery, if the remaining amount is below the set lower limit, the basal delivery will be stopped.

#### Simulink_requirement_item_32: Units conversion (Functional)
2.3 Units conversion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
Because bolus delivery and basal delivery are of different time scale. The units used for both of them will be different. The direct output of the bolus control chart is units/s. The direct output of basal control chart is Units/hr. Both of them needs to be converted to rev/min for the speed controller to react. Information of the hardware shall be provided to enable accurate unit conversion. Here is the required information:
1. Number of unit of medicine per mm^3
2. Cross-sectional area of reservoir in mm^2
3. Lead screw parameter inch/rev
4. Gear reduction ratio

##### Simulink_requirement_item_33: Convert Bolus Magnitude (Functional)
2.3.1 Convert Bolus Magnitude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
This portion of the controller shall convert units/s to rev/min.

##### Simulink_requirement_item_34: Convert Basal Rate (Functional)
2.3.2 Convert Basal Rate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
This portion of the controller shall convert units/hr to rev/min.

##### Simulink_requirement_item_35: Composition of delivery rate (Functional)
2.3.3 Composition of delivery rate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
Because the basal rate is usually very low compared with bolus magnitude, the algorithm shall add the two speed command together to get

##### Simulink_requirement_item_36: Convert displacement measurement into number of units (Functional)
2.3.4 Convert displacement measurement into number of units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
The direct measurement from the piston shall be in distance. The algorithm shall convert its unit in distance into number of units

### Simulink_requirement_item_37: Motor Speed Controller (Functional)
3. Motor Speed Controller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
The speed controller for the motor shall achieve the desired speed with adequate accuracy by controlling voltage. The feedback measurement is used to enhance the transient performance.

#### Simulink_requirement_item_38: Reference motor speed limit (Functional)
3.1 Reference motor speed limit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
Due to the hardware limitation, the reference speed shall be bounded between lower and upper limit.

#### Simulink_requirement_item_39: Reference motor speed filter (Functional)
3.2 Reference motor speed filter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
The reference motor speed shall be filtered by a low pass filter

#### Simulink_requirement_item_40: Feedforward lookup table based on reference motor speed (Functional)
3.3 Feedforward lookup table based on reference motor speed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
The controller shall be able to change the motor speed based on reference motor speed. The lookup table shall be calibrated using steady state test.

#### Simulink_requirement_item_41: Feedback Controller (Functional)
3.4 Feedback Controller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
The feedback part of this controller shall minimize speed error when the pump is working with parameter setting that is different from the steady state. The controller shall have the following features:

##### Simulink_requirement_item_42: 1. controller shall be driven by the different between reference motor speed ... (Functional)
1. controller shall be driven by the different between reference motor speed and actual motor speed

##### Simulink_requirement_item_43: 2. controller shall be a PI structure (Functional)

##### Simulink_requirement_item_44: 3. controller P gain shall be tunable with respect to different speed (Functional)

##### Simulink_requirement_item_45: 4. controller I gain shall be tunable with respect to different speed (Functional)

#### Simulink_requirement_item_46: Superimpose Command (Functional)
3.5 Superimpose Command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
The feedforward controller and the feedback controller shall be combined together.

#### Simulink_requirement_item_47: Voltage Command Rate Limitation (Functional)
3.6 Voltage Command Rate Limitation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
Considering the power limitation, the voltage command rate shall be limited to +-10 volts/s

### Simulink_requirement_item_57: Fault Detector (Functional)
4. Fault Detector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
The function of the Fault Detector is to trigger the alert when a physical occlusion is happening. The fault detector needs report occlusion within 30 seconds of the event.
There could be two options of fault detector:

#### Simulink_requirement_item_61: Occlusion Detection Option 1 (Functional)
4.1 Occlusion Detection Option 1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
The specific algorithm is designed based on signal processing and constant threshold.

#### Simulink_requirement_item_62: Occlusion Detection Option 2 (Functional)
4.2 Occlusion Detection Option 2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
The specific algorithm is designed based on Support Vector Machine (SVM).
